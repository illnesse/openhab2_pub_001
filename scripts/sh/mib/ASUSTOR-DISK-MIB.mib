ASUSTOR-DISK-MIB DEFINITIONS ::= BEGIN

IMPORTS
	OBJECT-GROUP, MODULE-COMPLIANCE
				FROM SNMPv2-CONF
	enterprises, MODULE-IDENTITY, OBJECT-TYPE, Integer32
				FROM SNMPv2-SMI;

asustor	 OBJECT IDENTIFIER 
	::= { enterprises 44738 }

asustorDisk MODULE-IDENTITY
    ORGANIZATION "www.asustor.com"
    CONTACT-INFO
         "postal: ASUSTOR Inc.
		 email: support@asustor.com"
    DESCRIPTION
        "Characteristics of the disk information"
    ::= { asustor 4 }
	
diskTable OBJECT-TYPE
    SYNTAX	   SEQUENCE OF DiskEntry
    MAX-ACCESS	  not-accessible
    STATUS	   current
    DESCRIPTION
    "Asustor disk table"
    ::= { asustorDisk 1 }

diskEntry	  OBJECT-TYPE
    SYNTAX	   DiskEntry
    MAX-ACCESS	  not-accessible
    STATUS	   current
    DESCRIPTION
    "For all disk entry"
    INDEX   { diskIndex }
    ::= { diskTable 1 }

DiskEntry ::= SEQUENCE {
    diskIndex		Integer32,
    diskID			OCTET STRING,
	diskModel		OCTET STRING,
	diskType		OCTET STRING,
	diskStatus		OCTET STRING,
	diskTemperature	Integer32,
	diskSize    Integer32,
	diskSmartInfo	OCTET STRING
}

diskIndex OBJECT-TYPE
    SYNTAX	   Integer32(0..2147483647)
    MAX-ACCESS	  not-accessible
    STATUS	   current
    DESCRIPTION
    "The index of disk table"
    ::= { diskEntry 1 }

diskID OBJECT-TYPE
    SYNTAX	  OCTET STRING
    MAX-ACCESS  read-only
    STATUS	  current
    DESCRIPTION
    "The disk bay"
    ::= { diskEntry 2 }

diskModel OBJECT-TYPE
    SYNTAX	  OCTET STRING
    MAX-ACCESS  read-only
    STATUS	  current
    DESCRIPTION
    "The disk model name"
    ::= { diskEntry 3 }

diskType OBJECT-TYPE
    SYNTAX	  OCTET STRING
    MAX-ACCESS  read-only
    STATUS	  current
    DESCRIPTION
    "The disk type, including SATA, SSD."
    ::= { diskEntry 4 }

diskStatus OBJECT-TYPE
    SYNTAX	  OCTET STRING
    MAX-ACCESS  read-only
    STATUS	  current
    DESCRIPTION
    "Asustor disk smart status 
	 Each meanings of status represented describe below.

	 Healthy: The hard disk smart status is healthy.
	 Normal: The hard disk smart status is normal.
	 Risky:	The hard disk smart status is risky.	
	 Dangerous: The hard disk smart status is dangerous.
	 Bad: The hard disk smart status is bad.
	"
    ::= { diskEntry 5 }

diskTemperature OBJECT-TYPE
    SYNTAX	   Integer32
    MAX-ACCESS	  read-only
    STATUS	   current
    DESCRIPTION
    "The temperature of each disk uses Celsius degree"
    ::= { diskEntry 6 }	
	
diskSize OBJECT-TYPE
    SYNTAX	   Integer32
    MAX-ACCESS	  read-only
    STATUS	   current
    DESCRIPTION
    "The disk size of disk uses gigabyte(GB)"
    ::= { diskEntry 7 }		
	
diskSmartInfo OBJECT-TYPE
    SYNTAX	   OCTET STRING
    MAX-ACCESS	  read-only
    STATUS	   current
    DESCRIPTION
    ""
    ::= { diskEntry 8 }			
	
asustorVolume MODULE-IDENTITY
    ORGANIZATION "www.asustor.com"
    CONTACT-INFO
         "postal:   Ccyuan Chen
          email:    ccyuanchen@asustor.com"
    DESCRIPTION
        "Characteristics of the volume information"
    ::= { asustor 5 }
    
volumeTable OBJECT-TYPE
    SYNTAX	   SEQUENCE OF VolumeEntry
    MAX-ACCESS	  not-accessible
    STATUS	   current
    DESCRIPTION
    "The volume table"
    ::= { asustorVolume 1 }

volumeEntry	  OBJECT-TYPE
    SYNTAX	   VolumeEntry
    MAX-ACCESS	  not-accessible
    STATUS	   current
    DESCRIPTION
    "For all volume entry"
    INDEX   { volumeIndex }
    ::= { volumeTable 1 }

VolumeEntry ::= SEQUENCE {
    volumeIndex		Integer32,
    volumeName		OCTET STRING,
	volumeLevel		OCTET STRING,
	volumeStatus		OCTET STRING,
	volumeFileSystem		OCTET STRING,
	volumeTotalSize  Integer32,
	volumeFreeSize  Integer32
}

volumeIndex OBJECT-TYPE
    SYNTAX	   Integer32(0..2147483647)
    MAX-ACCESS	  not-accessible
    STATUS	   current
    DESCRIPTION
    "The index of volume table"
    ::= { volumeEntry 1 }

volumeName OBJECT-TYPE
    SYNTAX	  OCTET STRING
    MAX-ACCESS  read-only
    STATUS	  current
    DESCRIPTION
    "The volume name"
    ::= { volumeEntry 2 }	
	
volumeLevel	 OBJECT-TYPE
    SYNTAX	  OCTET STRING
    MAX-ACCESS  read-only
    STATUS	  current
    DESCRIPTION
    "The volume level
	 Each meanings of volume level represented describe below.
	 
	 signal: The hard disk raid level is single 
	 jbod: The hard disk raid level is linear
	 raid0: The hard disk raid level is raid0
	 raid1: The hard disk raid level is raid1
	 raid10: The hard disk raid level is raid10
	 raid5: The hard disk raid level is raid5
	 raid6: The hard disk raid level is raid6	 
	"
    ::= { volumeEntry 3 }	
	
volumeStatus OBJECT-TYPE
    SYNTAX	  OCTET STRING
    MAX-ACCESS  read-only
    STATUS	  current
    DESCRIPTION
    "The volume status
	 Each meanings of volume level represented describe below.

	 healthy: The state of this RAID is healthy.
	 clean: The state of this RAID is clean.
	 active: The state of this RAID is active.
	 resyncing: The state of this RAID is resyncing.
	 recovering: The state of this RAID is recovering
	 reshaping: The state of this RAID is reshaping.
	 appending: The state of this RAID is appending.
	 migrating: The state of this RAID is migrating.
	 fsexpanding: The state of this RAID is expanding FS.
	 fsiniting: The state of this RAID is initializing FS.
	 degraded: The state of this RAID is healthy.
	 failed: The state of this RAID is failed.
	 inactive: The state of this RAID is inactive.
	"
    ::= { volumeEntry 4 }

volumeFileSystem	 OBJECT-TYPE
    SYNTAX	  OCTET STRING
    MAX-ACCESS  read-only
    STATUS	  current
    DESCRIPTION
    "The volume file system"
    ::= { volumeEntry 5 }

volumeTotalSize	 OBJECT-TYPE
    SYNTAX	  Integer32
    MAX-ACCESS  read-only
    STATUS	  current
    DESCRIPTION
    "The size of volume uses gigabyte(GB)"
    ::= { volumeEntry 6 }

volumeFreeSize  OBJECT-TYPE
    SYNTAX	  Integer32
    MAX-ACCESS  read-only
    STATUS	  current
    DESCRIPTION
    "The remain size of volume uses gigabyte(GB)"
    ::= { volumeEntry 7 }	
	
	
	
diskConformance OBJECT IDENTIFIER ::= { asustorDisk 2 }
diskCompliances OBJECT IDENTIFIER ::= { diskConformance 1 }
diskGroups 		OBJECT IDENTIFIER ::= { diskConformance 2 }

diskCompliance MODULE-COMPLIANCE
    STATUS  current
    DESCRIPTION
            "The compliance statement for asustorDisk entities which
            implement the ASUSTOR DISK MIB."
    MODULE  -- this module
        MANDATORY-GROUPS { diskGroup }

    ::= { diskCompliances 1 }

diskGroup OBJECT-GROUP
    OBJECTS { diskID,
              diskModel,
              diskType,
              diskStatus,
              diskTemperature}
    STATUS  current
    DESCRIPTION
            "A collection of objects providing basic information
             of an asustor disk entity."
    ::= { diskGroups 1 }

END
